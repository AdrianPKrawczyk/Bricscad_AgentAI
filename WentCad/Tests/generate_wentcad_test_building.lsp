;;; generate_wentcad_test_building.lsp
;;; Test environment for WentCad.
;;; Load in BricsCAD and run: GEN_WENTCAD_TEST_BUILDING
;;; Units: 1 DWG unit = 1 cm. Room areas are stored in m2, heights in m.

(vl-load-com)

(setq *wc-test-boundary-layer* "WC_TEST_OBRYSY")
(setq *wc-test-tag-layer* "WC_TEST_METKI")
(setq *wc-test-wall-layer* "WC_TEST_SCIANY")
(setq *wc-test-window-layer* "WC_TEST_OKNA")
(setq *wc-test-door-layer* "WC_TEST_DRZWI")
(setq *wc-test-note-layer* "WC_TEST_OPISY")
(setq *wc-test-window-note-layer* "WC_TEST_OPISY_OKIEN")
(setq *wc-test-door-note-layer* "WC_TEST_OPISY_DRZWI")
(setq *wc-test-floor-layer* "_WENTCAD_KONDYGNACJE")
(setq *wc-test-tag-block* "WC_ROOM_TAG_CM")
(setq *wc-test-window-block* "WC_WINDOW_CM")
(setq *wc-test-window-label-block* "WC_WINDOW_LABEL_CM")
(setq *wc-test-door-block* "WC_DOOR_CM")
(setq *wc-test-door-label-block* "WC_DOOR_LABEL_CM")
(setq *wc-test-wall-thickness* 12.0)

(defun wc:acad () (vlax-get-acad-object))
(defun wc:doc () (vla-get-ActiveDocument (wc:acad)))
(defun wc:model () (vla-get-ModelSpace (wc:doc)))

(defun wc:pt (x y z)
  (vlax-3d-point (list x y z))
)

(defun wc:ensure-layer (name color / layers layer)
  (setq layers (vla-get-Layers (wc:doc)))
  (setq layer (vl-catch-all-apply 'vla-Item (list layers name)))
  (if (vl-catch-all-error-p layer)
    (setq layer (vla-Add layers name))
  )
  (vla-put-Color layer color)
  layer
)

(defun wc:lwpoly (points layer color closed / arr idx pl)
  (setq arr (vlax-make-safearray vlax-vbDouble (cons 0 (- (* 2 (length points)) 1))))
  (setq idx 0)
  (foreach p points
    (vlax-safearray-put-element arr idx (car p))
    (setq idx (1+ idx))
    (vlax-safearray-put-element arr idx (cadr p))
    (setq idx (1+ idx))
  )
  (setq pl (vla-AddLightWeightPolyline (wc:model) (vlax-make-variant arr)))
  (vla-put-Layer pl layer)
  (vla-put-Color pl color)
  (vla-put-Closed pl (if closed :vlax-true :vlax-false))
  pl
)

(defun wc:rect (x1 y1 x2 y2 layer color)
  (wc:lwpoly (list (list x1 y1) (list x2 y1) (list x2 y2) (list x1 y2)) layer color T)
)

(defun wc:line (x1 y1 x2 y2 layer color / ln)
  (setq ln (vla-AddLine (wc:model) (wc:pt x1 y1 0.0) (wc:pt x2 y2 0.0)))
  (vla-put-Layer ln layer)
  (vla-put-Color ln color)
  ln
)

(defun wc:text (txt x y h layer color / obj)
  (setq obj (vla-AddText (wc:model) txt (wc:pt x y 0.0) h))
  (vla-put-Layer obj layer)
  (vla-put-Color obj color)
  obj
)

(defun wc:add-attribute (blk tag prompt default x y h)
  (vla-AddAttribute blk h 0 prompt (wc:pt x y 0.0) tag default)
)

(defun wc:ensure-tag-block (/ blocks blk exists)
  (setq blocks (vla-get-Blocks (wc:doc)))
  (setq exists (vl-catch-all-apply 'vla-Item (list blocks *wc-test-tag-block*)))
  (if (vl-catch-all-error-p exists)
    (progn
      (setq blk (vla-Add blocks (wc:pt 0.0 0.0 0.0) *wc-test-tag-block*))
      (vla-put-Layer (vla-AddLine blk (wc:pt -50.0 -24.0 0.0) (wc:pt 50.0 -24.0 0.0)) "0")
      (vla-put-Layer (vla-AddLine blk (wc:pt 50.0 -24.0 0.0) (wc:pt 50.0 24.0 0.0)) "0")
      (vla-put-Layer (vla-AddLine blk (wc:pt 50.0 24.0 0.0) (wc:pt -50.0 24.0 0.0)) "0")
      (vla-put-Layer (vla-AddLine blk (wc:pt -50.0 24.0 0.0) (wc:pt -50.0 -24.0 0.0)) "0")
      (wc:add-attribute blk "NR" "Numer pomieszczenia" "0.00" -42.0 8.0 10.0)
      (wc:add-attribute blk "NAZWA" "Nazwa pomieszczenia" "Pomieszczenie" -42.0 -4.0 8.0)
      (wc:add-attribute blk "H" "Wysokosc netto" "3.00" -42.0 -16.0 7.0)
      (wc:add-attribute blk "POW" "Powierzchnia" "0.00" 4.0 -16.0 7.0)
    )
  )
)

(defun wc:ensure-window-block (/ blocks blk exists)
  (setq blocks (vla-get-Blocks (wc:doc)))
  (setq exists (vl-catch-all-apply 'vla-Item (list blocks *wc-test-window-block*)))
  (if (vl-catch-all-error-p exists)
    (progn
      (setq blk (vla-Add blocks (wc:pt 0.0 0.0 0.0) *wc-test-window-block*))
      (vla-put-Layer (vla-AddLine blk (wc:pt -50.0 0.0 0.0) (wc:pt 50.0 0.0 0.0)) "0")
      (vla-put-Layer (vla-AddLine blk (wc:pt -50.0 -4.0 0.0) (wc:pt 50.0 -4.0 0.0)) "0")
      (vla-put-Layer (vla-AddLine blk (wc:pt -50.0 4.0 0.0) (wc:pt 50.0 4.0 0.0)) "0")
      (wc:add-attribute blk "WIDTH" "Szerokosc okna cm" "150" -45.0 14.0 6.0)
      (wc:add-attribute blk "HEIGHT" "Wysokosc okna cm" "150" -45.0 25.0 6.0)
      (wc:add-attribute blk "SILL" "Wysokosc parapetu cm" "90" -45.0 36.0 6.0)
    )
  )
)

(defun wc:ensure-window-label-block (/ blocks blk exists)
  (setq blocks (vla-get-Blocks (wc:doc)))
  (setq exists (vl-catch-all-apply 'vla-Item (list blocks *wc-test-window-label-block*)))
  (if (vl-catch-all-error-p exists)
    (progn
      (setq blk (vla-Add blocks (wc:pt 0.0 0.0 0.0) *wc-test-window-label-block*))
      (vla-put-Layer (vla-AddLine blk (wc:pt -45.0 -16.0 0.0) (wc:pt 45.0 -16.0 0.0)) "0")
      (vla-put-Layer (vla-AddLine blk (wc:pt 45.0 -16.0 0.0) (wc:pt 45.0 16.0 0.0)) "0")
      (vla-put-Layer (vla-AddLine blk (wc:pt 45.0 16.0 0.0) (wc:pt -45.0 16.0 0.0)) "0")
      (vla-put-Layer (vla-AddLine blk (wc:pt -45.0 16.0 0.0) (wc:pt -45.0 -16.0 0.0)) "0")
      (wc:add-attribute blk "WIDTH" "Szerokosc okna cm" "150" -36.0 4.0 6.0)
      (wc:add-attribute blk "HEIGHT" "Wysokosc okna cm" "150" -36.0 -8.0 6.0)
      (wc:add-attribute blk "SILL" "Wysokosc parapetu cm" "90" 8.0 -8.0 6.0)
    )
  )
)

(defun wc:ensure-door-block (/ blocks blk exists)
  (setq blocks (vla-get-Blocks (wc:doc)))
  (setq exists (vl-catch-all-apply 'vla-Item (list blocks *wc-test-door-block*)))
  (if (vl-catch-all-error-p exists)
    (progn
      (setq blk (vla-Add blocks (wc:pt 0.0 0.0 0.0) *wc-test-door-block*))
      (vla-put-Layer (vla-AddLine blk (wc:pt -45.0 0.0 0.0) (wc:pt 45.0 0.0 0.0)) "0")
      (vla-put-Layer (vla-AddLine blk (wc:pt -45.0 0.0 0.0) (wc:pt 20.0 55.0 0.0)) "0")
      (vla-put-Layer (vla-AddLine blk (wc:pt 45.0 0.0 0.0) (wc:pt 20.0 55.0 0.0)) "0")
      (wc:add-attribute blk "WIDTH" "Szerokosc drzwi cm" "90" -42.0 68.0 6.0)
      (wc:add-attribute blk "HEIGHT" "Wysokosc drzwi cm" "205" -42.0 79.0 6.0)
      (wc:add-attribute blk "SILL" "Prog cm" "0" -42.0 90.0 6.0)
    )
  )
)

(defun wc:ensure-door-label-block (/ blocks blk exists)
  (setq blocks (vla-get-Blocks (wc:doc)))
  (setq exists (vl-catch-all-apply 'vla-Item (list blocks *wc-test-door-label-block*)))
  (if (vl-catch-all-error-p exists)
    (progn
      (setq blk (vla-Add blocks (wc:pt 0.0 0.0 0.0) *wc-test-door-label-block*))
      (vla-put-Layer (vla-AddLine blk (wc:pt -45.0 -16.0 0.0) (wc:pt 45.0 -16.0 0.0)) "0")
      (vla-put-Layer (vla-AddLine blk (wc:pt 45.0 -16.0 0.0) (wc:pt 45.0 16.0 0.0)) "0")
      (vla-put-Layer (vla-AddLine blk (wc:pt 45.0 16.0 0.0) (wc:pt -45.0 16.0 0.0)) "0")
      (vla-put-Layer (vla-AddLine blk (wc:pt -45.0 16.0 0.0) (wc:pt -45.0 -16.0 0.0)) "0")
      (wc:add-attribute blk "WIDTH" "Szerokosc drzwi cm" "90" -36.0 4.0 6.0)
      (wc:add-attribute blk "HEIGHT" "Wysokosc drzwi cm" "205" -36.0 -8.0 6.0)
      (wc:add-attribute blk "SILL" "Prog cm" "0" 8.0 -8.0 6.0)
    )
  )
)

(defun wc:set-attrs (br values / attrs tag pair)
  (setq attrs (vlax-invoke br 'GetAttributes))
  (foreach att attrs
    (setq tag (strcase (vla-get-TagString att)))
    (setq pair (assoc tag values))
    (if pair
      (vla-put-TextString att (cdr pair))
    )
  )
)

(defun wc:tag (x y nr name h area / br)
  (setq br (vla-InsertBlock (wc:model) (wc:pt x y 0.0) *wc-test-tag-block* 1.0 1.0 1.0 0.0))
  (vla-put-Layer br *wc-test-tag-layer*)
  (vla-put-Color br 4)
  (wc:set-attrs br
    (list
      (cons "NR" nr)
      (cons "NAZWA" name)
      (cons "H" h)
      (cons "POW" area)
    )
  )
  br
)

(defun wc:window (x y rot width height sill / br)
  (setq br (vla-InsertBlock (wc:model) (wc:pt x y 0.0) *wc-test-window-block* (/ width 100.0) 1.0 1.0 rot))
  (vla-put-Layer br *wc-test-window-layer*)
  (vla-put-Color br 5)
  (wc:set-attrs br
    (list
      (cons "WIDTH" (rtos width 2 0))
      (cons "HEIGHT" (rtos height 2 0))
      (cons "SILL" (rtos sill 2 0))
    )
  )
  br
)

(defun wc:window-label (x y width height sill / br)
  (setq br (vla-InsertBlock (wc:model) (wc:pt x y 0.0) *wc-test-window-label-block* 1.0 1.0 1.0 0.0))
  (vla-put-Layer br *wc-test-window-note-layer*)
  (vla-put-Color br 6)
  (wc:set-attrs br
    (list
      (cons "WIDTH" (rtos width 2 0))
      (cons "HEIGHT" (rtos height 2 0))
      (cons "SILL" (rtos sill 2 0))
    )
  )
  br
)

(defun wc:door (x y rot width height sill / br)
  (setq br (vla-InsertBlock (wc:model) (wc:pt x y 0.0) *wc-test-door-block* (/ width 90.0) 1.0 1.0 rot))
  (vla-put-Layer br *wc-test-door-layer*)
  (vla-put-Color br 1)
  (wc:set-attrs br
    (list
      (cons "WIDTH" (rtos width 2 0))
      (cons "HEIGHT" (rtos height 2 0))
      (cons "SILL" (rtos sill 2 0))
    )
  )
  br
)

(defun wc:door-label (x y width height sill / br)
  (setq br (vla-InsertBlock (wc:model) (wc:pt x y 0.0) *wc-test-door-label-block* 1.0 1.0 1.0 0.0))
  (vla-put-Layer br *wc-test-door-note-layer*)
  (vla-put-Color br 30)
  (wc:set-attrs br
    (list
      (cons "WIDTH" (rtos width 2 0))
      (cons "HEIGHT" (rtos height 2 0))
      (cons "SILL" (rtos sill 2 0))
    )
  )
  br
)

(defun wc:room (x1 y1 x2 y2 nr name h area / cx cy)
  (wc:rect x1 y1 x2 y2 *wc-test-boundary-layer* 1)
  (setq cx (/ (+ x1 x2) 2.0))
  (setq cy (/ (+ y1 y2) 2.0))
  (wc:tag cx cy nr name h area)
)

(defun wc:walls-for-floor (x0 y0 / x1 y1 x2 y2 wt)
  (setq x1 x0)
  (setq y1 y0)
  (setq x2 (+ x0 1800.0))
  (setq y2 (+ y0 1000.0))
  (setq wt *wc-test-wall-thickness*)
  ;; Architectural substrate: 1 unit = 1 cm, internal walls are 12 cm.
  (wc:rect x1 y1 x2 y2 *wc-test-wall-layer* 8)
  (wc:rect (+ x0 300.0) y0 (+ x0 300.0 wt) (+ y0 400.0) *wc-test-wall-layer* 8)
  (wc:rect (+ x0 900.0) y0 (+ x0 900.0 wt) (+ y0 400.0) *wc-test-wall-layer* 8)
  (wc:rect x0 (+ y0 400.0) x2 (+ y0 400.0 wt) *wc-test-wall-layer* 8)
  (wc:rect (+ x0 800.0) (+ y0 400.0 wt) (+ x0 800.0 wt) y2 *wc-test-wall-layer* 8)
  ;; Legacy line windows plus semantic window blocks for WATT detection.
  (wc:line (+ x0 75.0) y0 (+ x0 225.0) y0 *wc-test-window-layer* 5)
  (wc:line (+ x0 1200.0) y2 (+ x0 1500.0) y2 *wc-test-window-layer* 5)
  (wc:window (+ x0 150.0) y0 0.0 150.0 150.0 90.0)
  (wc:window-label (+ x0 150.0) (- y0 70.0) 150.0 150.0 90.0)
  (wc:window (+ x0 1350.0) y2 0.0 200.0 120.0 85.0)
  (wc:window-label (+ x0 1350.0) (+ y2 70.0) 200.0 120.0 85.0)
  ;; Diagnostic: window close to an interior wall; scanner should leave it unassigned.
  (wc:window (+ x0 306.0) (+ y0 200.0) 1.5707963268 120.0 140.0 90.0)
  ;; Doors: one external and several internal, to verify DRZ assignment to SZ/SW.
  (wc:door x0 (+ y0 105.0) 1.5707963268 90.0 205.0 0.0)
  (wc:door-label (- x0 90.0) (+ y0 105.0) 90.0 205.0 0.0)
  (wc:door (+ x0 306.0) (+ y0 105.0) 1.5707963268 90.0 205.0 0.0)
  (wc:door-label (+ x0 390.0) (+ y0 105.0) 90.0 205.0 0.0)
  (wc:door (+ x0 906.0) (+ y0 200.0) 1.5707963268 90.0 205.0 0.0)
  (wc:door-label (+ x0 990.0) (+ y0 200.0) 90.0 205.0 0.0)
  (wc:door (+ x0 806.0) (+ y0 700.0) 1.5707963268 90.0 205.0 0.0)
  (wc:door-label (+ x0 890.0) (+ y0 700.0) 90.0 205.0 0.0)
)

(defun wc:make-parter ()
  (wc:text "KONDYGNACJA: Parter" 0.0 -170.0 80.0 *wc-test-note-layer* 7)
  (wc:rect -50.0 -50.0 1850.0 1050.0 *wc-test-floor-layer* 3)
  (wc:walls-for-floor 0.0 0.0)
  (wc:room 0.0 0.0 300.0 400.0 "0.01" "Wiatrolap" "3.00" "12.00")
  (wc:room 312.0 0.0 900.0 400.0 "0.02" "Komunikacja" "3.00" "23.52")
  (wc:room 912.0 0.0 1800.0 400.0 "0.03" "Biuro" "3.00" "35.52")
  (wc:room 0.0 412.0 800.0 1000.0 "0.04" "Sala spotkan" "3.00" "47.04")
  (wc:room 812.0 412.0 1800.0 1000.0 "0.05" "Open space" "3.00" "58.09")
)

(defun wc:make-pietro ()
  (wc:text "KONDYGNACJA: Pietro_1" 0.0 1180.0 80.0 *wc-test-note-layer* 7)
  (wc:rect -50.0 1250.0 1850.0 2350.0 *wc-test-floor-layer* 3)
  (wc:walls-for-floor 0.0 1300.0)
  (wc:room 0.0 1300.0 300.0 1700.0 "1.01" "Gabinet" "3.20" "12.00")
  (wc:room 312.0 1300.0 900.0 1700.0 "1.02" "Pokoj pracy" "3.20" "23.52")
  (wc:room 912.0 1300.0 1800.0 1700.0 "1.03" "Archiwum" "3.20" "35.52")
  (wc:room 0.0 1712.0 800.0 2300.0 "1.04" "Sala szkolen" "3.20" "47.04")
  (wc:room 812.0 1712.0 1800.0 2300.0 "1.05" "Socjal" "3.20" "58.09")
)

(defun wc:make-diagnostics ()
  (wc:text "PRZYPADKI DIAGNOSTYCZNE" 2100.0 -170.0 65.0 *wc-test-note-layer* 1)
  ;; Closed boundary without tag.
  (wc:rect 2100.0 0.0 2500.0 300.0 *wc-test-boundary-layer* 1)
  (wc:text "Obrys bez metki" 2100.0 330.0 35.0 *wc-test-note-layer* 1)
  ;; Tag outside any room.
  (wc:tag 2750.0 150.0 "X.01" "Metka poza obrysem" "3.00" "0.00")
  (wc:text "Metka poza obrysem" 2650.0 330.0 35.0 *wc-test-note-layer* 1)
  ;; Open boundary.
  (wc:lwpoly (list (list 2100.0 550.0) (list 2500.0 550.0) (list 2500.0 850.0) (list 2100.0 850.0)) *wc-test-boundary-layer* 1 nil)
  (wc:tag 2300.0 700.0 "X.02" "Obrys otwarty" "3.00" "12.00")
  (wc:text "Nie zamkniety obrys" 2100.0 900.0 35.0 *wc-test-note-layer* 1)
)

(defun wc:setup-layers ()
  (wc:ensure-layer *wc-test-boundary-layer* 1)
  (wc:ensure-layer *wc-test-tag-layer* 4)
  (wc:ensure-layer *wc-test-wall-layer* 8)
  (wc:ensure-layer *wc-test-window-layer* 5)
  (wc:ensure-layer *wc-test-door-layer* 1)
  (wc:ensure-layer *wc-test-note-layer* 7)
  (wc:ensure-layer *wc-test-window-note-layer* 6)
  (wc:ensure-layer *wc-test-door-note-layer* 30)
  (wc:ensure-layer *wc-test-floor-layer* 3)
)

(defun C:GEN_WENTCAD_TEST_BUILDING (/ oldcmdecho oldattreq oldattdia)
  (setq oldcmdecho (getvar "CMDECHO"))
  (setq oldattreq (getvar "ATTREQ"))
  (setq oldattdia (getvar "ATTDIA"))
  (setvar "CMDECHO" 0)
  (setvar "ATTREQ" 1)
  (setvar "ATTDIA" 0)

  (princ "\nWentCad: generowanie budynku testowego...")
  (wc:setup-layers)
  (wc:ensure-tag-block)
  (wc:ensure-window-block)
  (wc:ensure-window-label-block)
  (wc:ensure-door-block)
  (wc:ensure-door-label-block)
  (wc:make-parter)
  (wc:make-pietro)
  (wc:make-diagnostics)

  (setvar "CMDECHO" oldcmdecho)
  (setvar "ATTREQ" oldattreq)
  (setvar "ATTDIA" oldattdia)

  (princ "\n[SUKCES] Utworzono budynek testowy WentCad.")
  (princ "\nMapowanie WentCad:")
  (princ "\n  Warstwa obrysow: WC_TEST_OBRYSY")
  (princ "\n  Warstwa metek:   WC_TEST_METKI")
  (princ "\n  Atrybut numeru:  NR")
  (princ "\n  Atrybut nazwy:   NAZWA")
  (princ "\n  Atrybut wys.:    H")
  (princ "\n  Atrybut pow.:    POW")
  (princ "\nMapowanie WATT:")
  (princ "\n  Warstwa scian:        WC_TEST_SCIANY")
  (princ "\n  Warstwa okien:        WC_TEST_OKNA")
  (princ "\n  Warstwa opisow okien: WC_TEST_OPISY_OKIEN")
  (princ "\n  Warstwa drzwi:        WC_TEST_DRZWI")
  (princ "\n  Warstwa opisow drzwi: WC_TEST_OPISY_DRZWI")
  (princ "\n  Atrybuty otworow:     WIDTH, HEIGHT, SILL")
  (princ "\nJednostki: 1 jednostka DWG = 1 cm; powierzchnie w metkach sa w m2.")
  (princ "\nKondygnacje: Parter ok. -50,-50 do 1850,1050; Pietro_1 ok. -50,1250 do 1850,2350.")
  (princ)
)

(princ "\nZaladowano generator testowy WentCad. Uruchom: GEN_WENTCAD_TEST_BUILDING")
(princ)
